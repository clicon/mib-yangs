/*
 * This YANG module has been generated by smidump 0.5.0:
 *
 *      smidump -f yang NET-SNMP-EXAMPLES-MIB
 *
 * Do not edit. Edit the source file instead!
 */

module NET-SNMP-EXAMPLES-MIB {

  namespace "urn:ietf:params:xml:ns:yang:smiv2:NET-SNMP-EXAMPLES-MIB";
  prefix "net-snmp-examples";

  import INET-ADDRESS-MIB {
    prefix "inet-address";
  }

  import NET-SNMP-MIB {
    prefix "net-snmp";
  }

  import SNMP-FRAMEWORK-MIB {
    prefix "snmp-framework";
  }

  import SNMPv2-TC {
    prefix "snmpv2-tc";
  }

  import ietf-yang-smiv2 {
    prefix "smiv2";
  }

  organization
   "www.net-snmp.org";

  contact
   "postal:   Wes Hardaker
    P.O. Box 382
    Davis CA  95617
    
    email:    net-snmp-coders@lists.sourceforge.net";

  description
   "Example MIB objects for agent module example implementations";

  revision 2004-06-15 {
    description
     "Corrected notification example definitions";
  }

  revision 2002-02-06 {
    description
     "First draft";
  }


  container NET-SNMP-EXAMPLES-MIB {
    config false;

    container netSnmpExampleScalars {
      smiv2:oid "1.3.6.1.4.1.8072.2.1";

      leaf netSnmpExampleInteger {
        type int32;
        description
         "This is a simple object which merely houses a writable
          integer.  It's only purposes is to hold the value of a single
          integer.  Writing to it will simply change the value for
          subsequent GET/GETNEXT/GETBULK retrievals.
          
          This example object is implemented in the
          agent/mibgroup/examples/scalar_int.c file.";
        smiv2:defval "42";
        smiv2:max-access "read-write";
        smiv2:oid "1.3.6.1.4.1.8072.2.1.1";
      }

      leaf netSnmpExampleSleeper {
        type int32;
        description
         "This is a simple object which is a basic integer.  It's value
          indicates the number of seconds that the agent will take in
          responding to requests of this object.  This is implemented
          in a way which will allow the agent to keep responding to
          other requests while access to this object is blocked.  It is
          writable, and changing it's value will change the amount of
          time the agent will effectively wait for before returning a
          response when this object is manipulated.  Note that SET
          requests through this object will take longer, since the
          delay is applied to each internal transaction phase, which
          could result in delays of up to 4 times the value of this
          object.
          
          This example object is implemented in the
          agent/mibgroup/examples/delayed_instance.c file.";
        smiv2:defval "1";
        smiv2:max-access "read-write";
        smiv2:oid "1.3.6.1.4.1.8072.2.1.2";
      }

      leaf netSnmpExampleString {
        type snmp-framework:SnmpAdminString;
        description
         "This is a simple object which merely houses a writable
          string.  It's only purposes is to hold the value of a single
          string.  Writing to it will simply change the value for
          subsequent GET/GETNEXT/GETBULK retrievals.
          
          This example object is implemented in the
          agent/mibgroup/examples/watched.c file.";
        smiv2:defval "So long, and thanks for all the fish!";
        smiv2:max-access "read-write";
        smiv2:oid "1.3.6.1.4.1.8072.2.1.3";
      }
    }

    container netSnmpIETFWGTable {
      description
       "This table merely contains a set of data which is otherwise
        useless for true network management.  It is a table which
        describes properies about a IETF Working Group, such as the
        names of the two working group chairs.
        
        This example table is implemented in the
        agent/mibgroup/examples/data_set.c file.";
      smiv2:oid "1.3.6.1.4.1.8072.2.2.1";

      list netSnmpIETFWGEntry {
        key "nsIETFWGName";
        description
         "A row describing a given working group";
        smiv2:oid "1.3.6.1.4.1.8072.2.2.1.1";

        leaf nsIETFWGName {
          type binary {
            length "1..32";
          }
          description
           "The name of the IETF Working Group this table describes.";
          smiv2:max-access "not-accessible";
          smiv2:oid "1.3.6.1.4.1.8072.2.2.1.1.1";
        }

        leaf nsIETFWGChair1 {
          type binary;
          description
           "One of the names of the chairs for the IETF working group.";
          smiv2:max-access "read-write";
          smiv2:oid "1.3.6.1.4.1.8072.2.2.1.1.2";
        }

        leaf nsIETFWGChair2 {
          type binary;
          description
           "The other name, if one exists, of the chairs for the IETF
            working group.";
          smiv2:max-access "read-write";
          smiv2:oid "1.3.6.1.4.1.8072.2.2.1.1.3";
        }
      }
    }

    container netSnmpHostsTable {
      description
       "An example table that implements a wrapper around the
        /etc/hosts file on a machine using the iterator helper API.";
      smiv2:oid "1.3.6.1.4.1.8072.2.2.2";

      list netSnmpHostsEntry {
        key "netSnmpHostName";
        description
         "A host name mapped to an ip address";
        smiv2:oid "1.3.6.1.4.1.8072.2.2.2.1";

        leaf netSnmpHostName {
          type binary {
            length "0..64";
          }
          description
           "A host name that exists in the /etc/hosts (unix) file.";
          smiv2:max-access "not-accessible";
          smiv2:oid "1.3.6.1.4.1.8072.2.2.2.1.1";
        }

        leaf netSnmpHostAddressType {
          type inet-address:InetAddressType;
          description
           "The address type of then given host.";
          smiv2:max-access "read-write";
          smiv2:oid "1.3.6.1.4.1.8072.2.2.2.1.2";
        }

        leaf netSnmpHostAddress {
          type inet-address:InetAddress;
          description
           "The address of then given host.";
          smiv2:max-access "read-write";
          smiv2:oid "1.3.6.1.4.1.8072.2.2.2.1.3";
        }

        leaf netSnmpHostStorage {
          type snmpv2-tc:StorageType;
          description
           "The storage type for this conceptual row.";
          smiv2:defval "nonVolatile";
          smiv2:max-access "read-write";
          smiv2:oid "1.3.6.1.4.1.8072.2.2.2.1.4";
        }

        leaf netSnmpHostRowStatus {
          type snmpv2-tc:RowStatus;
          description
           "The status of this conceptual row.";
          smiv2:max-access "read-write";
          smiv2:oid "1.3.6.1.4.1.8072.2.2.2.1.5";
        }
      }
    }
  }

  notification netSnmpExampleHeartbeatNotification {
    description
     "An example notification, used to illustrate the
      definition and generation of trap and inform PDUs
      (including the use of both standard and additional
      varbinds in the notification payload).
      This notification will typically be sent every
       30 seconds, using the code found in the example module
          agent/mibgroup/examples/notification.c";
    smiv2:oid "1.3.6.1.4.1.8072.2.3.0.1";

    container object-1 {

      leaf netSnmpExampleHeartbeatRate {
        type int32;
        description
         "A simple integer object, to act as a payload for the
          netSnmpExampleHeartbeatNotification.  The value has
          no real meaning, but is nominally the interval (in
          seconds) between successive heartbeat notifications.";
        smiv2:max-access "accessible-for-notify";
        smiv2:oid "1.3.6.1.4.1.8072.2.3.2.1";
      }
    }
  }

  smiv2:alias "netSnmpExamples" {
    smiv2:oid "1.3.6.1.4.1.8072.2";
  }

  smiv2:alias "netSnmpExampleScalars" {
    smiv2:oid "1.3.6.1.4.1.8072.2.1";
  }

  smiv2:alias "netSnmpExampleTables" {
    smiv2:oid "1.3.6.1.4.1.8072.2.2";
  }

  smiv2:alias "netSnmpExampleNotifications" {
    smiv2:oid "1.3.6.1.4.1.8072.2.3";
  }

  smiv2:alias "netSnmpExampleNotificationPrefix" {
    smiv2:oid "1.3.6.1.4.1.8072.2.3.0";
  }

  smiv2:alias "netSnmpExampleNotificationObjects" {
    smiv2:oid "1.3.6.1.4.1.8072.2.3.2";
  }

}

/*
 * This YANG module has been generated by smidump 0.5.0:
 *
 *      smidump -f yang NET-SNMP-MIB
 *
 * Do not edit. Edit the source file instead!
 */

module NET-SNMP-MIB {

  namespace "urn:ietf:params:xml:ns:yang:smiv2:NET-SNMP-MIB";
  prefix "net-snmp";

  import ietf-yang-smiv2 {
    prefix "smiv2";
  }

  organization
   "www.net-snmp.org";

  contact
   "postal:   Wes Hardaker
    P.O. Box 382
    Davis CA  95617
    
    email:    net-snmp-coders@lists.sourceforge.net";

  description
   "Top-level infrastructure of the Net-SNMP project enterprise MIB tree";

  revision 2002-01-30 {
    description
     "First draft";
  }

  smiv2:alias "netSnmp" {
    smiv2:oid "1.3.6.1.4.1.8072";
  }

  smiv2:alias "netSnmpObjects" {
    smiv2:oid "1.3.6.1.4.1.8072.1";
  }

  smiv2:alias "netSnmpEnumerations" {
    smiv2:oid "1.3.6.1.4.1.8072.3";
  }

  smiv2:alias "netSnmpModuleIDs" {
    smiv2:oid "1.3.6.1.4.1.8072.3.1";
  }

  smiv2:alias "netSnmpAgentOIDs" {
    smiv2:oid "1.3.6.1.4.1.8072.3.2";
  }

  smiv2:alias "netSnmpDomains" {
    smiv2:oid "1.3.6.1.4.1.8072.3.3";
  }

  smiv2:alias "netSnmpNotificationPrefix" {
    smiv2:oid "1.3.6.1.4.1.8072.4";
  }

  smiv2:alias "netSnmpNotifications" {
    smiv2:oid "1.3.6.1.4.1.8072.4.0";
  }

  smiv2:alias "netSnmpNotificationObjects" {
    smiv2:oid "1.3.6.1.4.1.8072.4.1";
  }

  smiv2:alias "netSnmpConformance" {
    smiv2:oid "1.3.6.1.4.1.8072.5";
  }

  smiv2:alias "netSnmpCompliances" {
    smiv2:oid "1.3.6.1.4.1.8072.5.1";
  }

  smiv2:alias "netSnmpGroups" {
    smiv2:oid "1.3.6.1.4.1.8072.5.2";
  }

  smiv2:alias "netSnmpExperimental" {
    smiv2:oid "1.3.6.1.4.1.8072.9999";
  }

  smiv2:alias "netSnmpPlaypen" {
    smiv2:oid "1.3.6.1.4.1.8072.9999.9999";
  }

}

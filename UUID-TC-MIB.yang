/*
 * This YANG module has been generated by smidump 0.5.0:
 *
 *      smidump -f yang UUID-TC-MIB
 *
 * Do not edit. Edit the source file instead!
 */

module UUID-TC-MIB {

  namespace "urn:ietf:params:xml:ns:yang:smiv2:UUID-TC-MIB";
  prefix "uuid-tc";

  import ietf-yang-smiv2 {
    prefix "smiv2";
  }

  organization
   "IETF Energy Management Working Group";

  contact
   "WG Email: eman@ietf.org
    Mailing list subscription info:
    http://www.ietf.org/mailman/listinfo/eman
    
    Dan Romascanu
    Avaya
    Park Atidim, Bldg. #3
    Tel Aviv, 61581
    Israel
    Phone: +972-3-6458414
    Email: dromasca@avaya.com
    
    Juergen Quittek
    NEC Europe Ltd.
    Network Research Division
    Kurfuersten-Anlage 36
    Heidelberg  69115
    Germany
    Phone: +49 6221 4342-115
    Email: quittek@neclab.eu
    
    Mouli Chandramouli
    Cisco Systems, Inc.
    Sarjapur Outer Ring Road
    Bangalore 560103
    India
    Phone: +91 80 4429 2409
    Email: moulchan@cisco.com";

  description
   "This MIB module defines TEXTUAL-CONVENTIONs
    representing Universally Unique IDentifiers
    (UUIDs).
    
    Copyright (c) 2013 IETF Trust and the persons
    identified as authors of the code.  All rights
    reserved.
    
    Redistribution and use in source and binary forms,
    with or without modification, is permitted
    pursuant to, and subject to the license terms
    contained in, the Simplified BSD License set forth
    in Section 4.c of the IETF Trust's Legal
    Provisions Relating to IETF Documents
    (http://trustee.ietf.org/license-info).";

  revision 2013-04-05 {
    description
     "Initial version of this MIB as published in
      RFC 6933.";
  }

  typedef UUID {
    type string {
      length "16";
    }
    description
     "Universally Unique Identifier information.  The syntax must
      conform to RFC 4122, Section 4.1.";
    smiv2:display-hint "4x-2x-2x-1x1x-6x";
  }

  typedef UUIDorZero {
    type string {
      length "0|16";
    }
    description
     "Universally Unique Identifier information.  The syntax must
      conform to RFC 4122, Section 4.1.
      
      The semantics of the value zero-length OCTET STRING are
      object-specific and must therefore be defined as part of
      the description of any object that uses this syntax.";
    smiv2:display-hint "4x-2x-2x-1x1x-6x";
  }

  smiv2:alias "uuidTCMIB" {
    smiv2:oid "1.3.6.1.2.1.217";
  }

}

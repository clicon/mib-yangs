/*
 * This YANG module has been generated by smidump 0.5.0:
 *
 *      smidump -f yang CLIXON-TYPES-MIB
 *
 * Do not edit. Edit the source file instead!
 */

module CLIXON-TYPES-MIB {

  namespace "urn:ietf:params:xml:ns:yang:smiv2:CLIXON-TYPES-MIB";
  prefix "clixon-types";

  import IANAifType-MIB {
    prefix "ianaiftype-mib";
  }

  import INET-ADDRESS-MIB {
    prefix "inet-address";
  }

  import NET-SNMP-MIB {
    prefix "net-snmp";
  }

  import SNMP-FRAMEWORK-MIB {
    prefix "snmp-framework";
  }

  import SNMPv2-TC {
    prefix "snmpv2-tc";
  }

  import ietf-inet-types {
    prefix "inet";
  }

  import ietf-yang-smiv2 {
    prefix "smiv2";
  }

  import ietf-yang-types {
    prefix "yang";
  }

  organization
   "www.net-snmp.org";

  contact
   "postal:   Wes Hardaker
    P.O. Box 382
    Davis CA  95617
    email:    net-snmp-coders@lists.sourceforge.net";

  description
   "Example MIB objects for agent module example implementations";

  revision 2004-06-15 {
    description
     "Corrected notification example definitions";
  }

  revision 2002-02-06 {
    description
     "First draft";
  }


  container CLIXON-TYPES-MIB {
    config false;

    container netSnmp {
      smiv2:oid "1.3.6.1.4.1.8072";
    }

    container clixonExampleScalars {
      smiv2:oid "1.3.6.1.4.1.8072.200.1";

      leaf clixonExampleInteger {
        type int32;
        description
         "This is a simple object which merely houses a writable
          integer.  It's only purposes is to hold the value of a single
          integer.  Writing to it will simply change the value for
          subsequent GET/GETNEXT/GETBULK retrievals.
          This example object is implemented in the
          agent/mibgroup/examples/scalar_int.c file.";
        smiv2:defval "42";
        smiv2:max-access "read-write";
        smiv2:oid "1.3.6.1.4.1.8072.200.1.1";
      }

      leaf clixonExampleSleeper {
        type int32;
        description
         "This is a simple object which is a basic integer.  It's value
          indicates the number of seconds that the agent will take in
          responding to requests of this object.  This is implemented
          in a way which will allow the agent to keep responding to
          other requests while access to this object is blocked.  It is
          writable, and changing it's value will change the amount of
          time the agent will effectively wait for before returning a
          response when this object is manipulated.  Note that SET
          requests through this object will take longer, since the
          delay is applied to each internal transaction phase, which
          could result in delays of up to 4 times the value of this
          object.
          This example object is implemented in the
          agent/mibgroup/examples/delayed_instance.c file.";
        smiv2:defval "1";
        smiv2:max-access "read-write";
        smiv2:oid "1.3.6.1.4.1.8072.200.1.2";
      }

      leaf clixonExampleString {
        type snmp-framework:SnmpAdminString;
        description
         "This is a simple object which merely houses a writable
          string.  It's only purposes is to hold the value of a single
          string.  Writing to it will simply change the value for
          subsequent GET/GETNEXT/GETBULK retrievals.
          This example object is implemented in the
          agent/mibgroup/examples/watched.c file.";
        smiv2:defval "So long, and thanks for all the fish!";
        smiv2:max-access "read-write";
        smiv2:oid "1.3.6.1.4.1.8072.200.1.3";
      }

      leaf ifTableLastChange {
        type yang:timeticks;
        description
         "The value of sysUpTime at the time of the last creation or
          deletion of an entry in the ifTable.  If the number of
          entries has been unchanged since the last re-initialization
          of the local network management subsystem, then this object
          contains a zero value.";
        smiv2:max-access "read-only";
        smiv2:oid "1.3.6.1.4.1.8072.200.1.4";
      }

      leaf ifType {
        type ianaiftype-mib:IANAifType;
        description
         "The type of interface.  Additional values for ifType are
          assigned by the Internet Assigned Numbers Authority (IANA),
          through updating the syntax of the IANAifType textual
          convention.";
        smiv2:max-access "read-only";
        smiv2:oid "1.3.6.1.4.1.8072.200.1.5";
      }

      leaf ifSpeed {
        type yang:gauge32;
        description
         "An estimate of the interface's current bandwidth in bits
          per second.  For interfaces which do not vary in bandwidth
          or for those where no accurate estimation can be made, this
          object should contain the nominal bandwidth.  If the
          bandwidth of the interface is greater than the maximum value
          reportable by this object then this object should report its
          maximum value (4,294,967,295) and ifHighSpeed must be used
          to report the interace's speed.  For a sub-layer which has
          no concept of bandwidth, this object should be zero.";
        smiv2:max-access "read-only";
        smiv2:oid "1.3.6.1.4.1.8072.200.1.6";
      }

      leaf ifAdminStatus {
        type enumeration {
          enum "up" {
            value "1";
          }
          enum "down" {
            value "2";
          }
          enum "testing" {
            value "3";
          }
        }
        description
         "The desired state of the interface.  The testing(3) state
          indicates that no operational packets can be passed.  When a
          managed system initializes, all interfaces start with
          ifAdminStatus in the down(2) state.  As a result of either
          explicit management action or per configuration information
          retained by the managed system, ifAdminStatus is then
          changed to either the up(1) or testing(3) states (or remains
          in the down(2) state).";
        smiv2:max-access "read-write";
        smiv2:oid "1.3.6.1.4.1.8072.200.1.7";
      }

      leaf ifInOctets {
        type yang:counter32;
        description
         "The total number of octets received on the interface,
          including framing characters.
          Discontinuities in the value of this counter can occur at
          re-initialization of the management system, and at other
          times as indicated by the value of
          ifCounterDiscontinuityTime.";
        smiv2:max-access "read-only";
        smiv2:oid "1.3.6.1.4.1.8072.200.1.8";
      }

      leaf ifHCInOctets {
        type yang:counter64;
        description
         "The total number of octets received on the interface,
          including framing characters.  This object is a 64-bit
          version of ifInOctets.
          Discontinuities in the value of this counter can occur at
          re-initialization of the management system, and at other
          times as indicated by the value of
          ifCounterDiscontinuityTime.";
        smiv2:max-access "read-only";
        smiv2:oid "1.3.6.1.4.1.8072.200.1.9";
      }

      leaf ifPromiscuousMode {
        type boolean;
        description
         "This object has a value of false(2) if this interface only
          accepts packets/frames that are addressed to this station.
          This object has a value of true(1) when the station accepts
          all packets/frames transmitted on the media.  The value
          true(1) is only legal on certain types of media.  If legal,
          setting this object to a value of true(1) may require the
          interface to be reset before becoming effective.
          The value of ifPromiscuousMode does not affect the reception
          of broadcast and multicast packets/frames by the interface.";
        smiv2:max-access "read-write";
        smiv2:oid "1.3.6.1.4.1.8072.200.1.10";
      }

      leaf ifCounterDiscontinuityTime {
        type yang:timestamp;
        description
         "The value of sysUpTime on the most recent occasion at which
          any one or more of this interface's counters suffered a
          discontinuity.  The relevant counters are the specific
          instances associated with this interface of any Counter32 or
          Counter64 object contained in the ifTable or ifXTable.  If
          no such discontinuities have occurred since the last re-
          initialization of the local management subsystem, then this
          object contains a zero value.";
        smiv2:max-access "read-only";
        smiv2:oid "1.3.6.1.4.1.8072.200.1.11";
      }

      leaf ifStackStatus {
        type snmpv2-tc:RowStatus;
        description
         "The status of the relationship between two sub-layers.
          Changing the value of this object from 'active' to
          'notInService' or 'destroy' will likely have consequences up
          and down the interface stack.  Thus, write access to this
          object is likely to be inappropriate for some types of
          interfaces, and many implementations will choose not to
          support write-access for any type of interface.";
        smiv2:max-access "read-only";
        smiv2:oid "1.3.6.1.4.1.8072.200.1.12";
      }

      leaf ifIpAddr {
        type inet:ipv4-address;
        description
         "IP address example.";
        smiv2:max-access "read-write";
        smiv2:oid "1.3.6.1.4.1.8072.200.1.13";
      }

      leaf bitTest {
        type bits {
          bit alarmActive {
            position "0";
          }
          bit deviceRunning {
            position "1";
          }
          bit failure {
            position "2";
          }
        }
        description
         "Simple bits value used for testing.";
        smiv2:max-access "read-write";
        smiv2:oid "1.3.6.1.4.1.8072.200.1.14";
      }
    }

    container clixonIETFWGTable {
      description
       "This table merely contains a set of data which is otherwise
        useless for true network management.  It is a table which
        describes properies about a IETF Working Group, such as the
        names of the two working group chairs.
        This example table is implemented in the
        agent/mibgroup/examples/data_set.c file.";
      smiv2:oid "1.3.6.1.4.1.8072.200.2.1";

      list clixonIETFWGEntry {
        key "nsIETFWGName";
        description
         "A row describing a given working group";
        smiv2:oid "1.3.6.1.4.1.8072.200.2.1.1";

        leaf nsIETFWGName {
          type int32 {
            range "1..2147483647";
          }
          description
           "The name of the IETF Working Group this table describes.";
          smiv2:max-access "not-accessible";
          smiv2:oid "1.3.6.1.4.1.8072.200.2.1.1.1";
        }

        leaf nsIETFWGChair1 {
          type binary;
          description
           "One of the names of the chairs for the IETF working group.";
          smiv2:max-access "read-write";
          smiv2:oid "1.3.6.1.4.1.8072.200.2.1.1.2";
        }

        leaf nsIETFWGChair2 {
          type binary;
          description
           "The other name, if one exists, of the chairs for the IETF
            working group.";
          smiv2:max-access "read-write";
          smiv2:oid "1.3.6.1.4.1.8072.200.2.1.1.3";
        }
      }
    }

    container clixonHostsTable {
      description
       "An example table that implements a wrapper around the
        /etc/hosts file on a machine using the iterator helper API.";
      smiv2:oid "1.3.6.1.4.1.8072.200.2.2";

      list clixonHostsEntry {
        key "clixonHostName";
        description
         "A host name mapped to an ip address";
        smiv2:oid "1.3.6.1.4.1.8072.200.2.2.1";

        leaf clixonHostName {
          type binary {
            length "0..64";
          }
          description
           "A host name that exists in the /etc/hosts (unix) file.";
          smiv2:max-access "not-accessible";
          smiv2:oid "1.3.6.1.4.1.8072.200.2.2.1.1";
        }

        leaf clixonHostAddressType {
          type inet-address:InetAddressType;
          description
           "The address type of then given host.";
          smiv2:max-access "read-write";
          smiv2:oid "1.3.6.1.4.1.8072.200.2.2.1.2";
        }

        leaf clixonHostAddress {
          type inet-address:InetAddress;
          description
           "The address of then given host.";
          smiv2:max-access "read-write";
          smiv2:oid "1.3.6.1.4.1.8072.200.2.2.1.3";
        }

        leaf clixonHostStorage {
          type snmpv2-tc:StorageType;
          description
           "The storage type for this conceptual row.";
          smiv2:defval "nonVolatile";
          smiv2:max-access "read-write";
          smiv2:oid "1.3.6.1.4.1.8072.200.2.2.1.4";
        }

        leaf clixonHostRowStatus {
          type snmpv2-tc:RowStatus;
          description
           "The status of this conceptual row.";
          smiv2:max-access "read-write";
          smiv2:oid "1.3.6.1.4.1.8072.200.2.2.1.5";
        }
      }
    }

    container clixonInetTable {
      description
       "This table merely contains a set of data which is otherwise
        useless for true network management.  It is a table which
        describes properies about a IETF Working Group, such as the
        names of the two working group chairs.
        This example table is implemented in the
        agent/mibgroup/examples/data_set.c file.";
      smiv2:oid "1.3.6.1.4.1.8072.200.2.3";

      list clixonInetEntry {
        key "clixonAddress";
        description
         "A row describing a given working group";
        smiv2:oid "1.3.6.1.4.1.8072.200.2.3.1";

        leaf clixonAddress {
          type inet-address:InetAddress;
          description
           "The name of the IETF Working Group this table describes.";
          smiv2:max-access "not-accessible";
          smiv2:oid "1.3.6.1.4.1.8072.200.2.3.1.2";
        }

        leaf clixonString {
          type binary;
          description
           "One of the names of the chairs for the IETF working group.";
          smiv2:max-access "read-write";
          smiv2:oid "1.3.6.1.4.1.8072.200.2.3.1.3";
        }
      }
    }

    container clixonTable {
      description
       "This table merely contains a set of data which is otherwise
        useless for true network management.  It is a table which
        describes properies about a IETF Working Group, such as the
        names of the two working group chairs.
        This example table is implemented in the
        agent/mibgroup/examples/data_set.c file.";
      smiv2:oid "1.3.6.1.4.1.8072.200.4.1";

      list clixonEntry {
        key "nsName";
        description
         "A row describing a given working group";
        smiv2:oid "1.3.6.1.4.1.8072.200.4.1.1";

        leaf nsName {
          type int32 {
            range "1..2147483647";
          }
          description
           "The name of the IETF Working Group this table describes.";
          smiv2:max-access "not-accessible";
          smiv2:oid "1.3.6.1.4.1.8072.200.4.1.1.1";
        }

        leaf nsChair1 {
          type binary;
          description
           "One of the names of the chairs for the IETF working group.";
          smiv2:max-access "read-write";
          smiv2:oid "1.3.6.1.4.1.8072.200.4.1.1.2";
        }

        leaf nsChair2 {
          type binary;
          description
           "The other name, if one exists, of the chairs for the IETF
            working group.";
          smiv2:max-access "read-write";
          smiv2:oid "1.3.6.1.4.1.8072.200.4.1.1.3";
        }
      }
    }
  }

  smiv2:alias "clixonExamples" {
    smiv2:oid "1.3.6.1.4.1.8072.200";
  }

  smiv2:alias "clixonExampleScalars" {
    smiv2:oid "1.3.6.1.4.1.8072.200.1";
  }

  smiv2:alias "clixonExampleTables" {
    smiv2:oid "1.3.6.1.4.1.8072.200.2";
  }

  smiv2:alias "clixonExampleNotifications" {
    smiv2:oid "1.3.6.1.4.1.8072.200.3";
  }

  smiv2:alias "clixonExampleNotificationPrefix" {
    smiv2:oid "1.3.6.1.4.1.8072.200.3.0";
  }

  smiv2:alias "clixonExampleNotificationObjects" {
    smiv2:oid "1.3.6.1.4.1.8072.200.3.2";
  }

  smiv2:alias "clixonTables" {
    smiv2:oid "1.3.6.1.4.1.8072.200.4";
  }

  smiv2:alias "clixonInetTables" {
    smiv2:oid "1.3.6.1.4.1.8072.200.5";
  }

}
